--
-- Copyright (c) 2010 by Ruckus Wireless, Inc.
-- All Rights Reserved
--

RUCKUS-TC-MIB DEFINITIONS ::= BEGIN

IMPORTS
    ruckusCommonTCModule
        FROM RUCKUS-ROOT-MIB
    TEXTUAL-CONVENTION
        FROM SNMPv2-TC
    MODULE-IDENTITY,
    Integer32
        FROM SNMPv2-SMI;

ruckusTCMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "This is the mib module for defining all the textual
        conventions."
    ::= { ruckusCommonTCModule 1 }


RuckusRadioMode ::= TEXTUAL-CONVENTION
    STATUS current
    DESCRIPTION
        "Specifies the physical type of the radio."
    SYNTAX INTEGER {
            ieee802dot11b(1),
            ieee802dot11g(2),
            ieee802dot11Mixed(3),
            ieee802dot11a(4),
            ieee802dot11ng(5),
            ieee802dot11na(6) }


RuckusWEPKey ::= TEXTUAL-CONVENTION
    STATUS current
    DESCRIPTION
        "Specifies the WEP key."
    SYNTAX OCTET STRING (SIZE (5 | 13 | 10 | 26))


RuckusAdminStatus ::= TEXTUAL-CONVENTION
    STATUS current
    DESCRIPTION
        "Administrative status for ruckus managed object."
    SYNTAX INTEGER {
            enable(1),
            disable(2) }


RuckusCountryCode ::= TEXTUAL-CONVENTION
    STATUS current
    DESCRIPTION
        "Specifies the country code.
         Each country represented as a two character.

        Here is the list:

        ALBANIA            ->    AL
        ALGERIA            ->    DZ
        ARGENTINA          ->    AR
        ARMENIA            ->    AM
        AUSTRALIA          ->    AU
        AUSTRIA            ->    AT
        AZERBAIJAN         ->    AZ
        BAHRAIN            ->    BH
        BELARUS            ->    BY
        BELGIUM            ->    BE
        BELIZE             ->    BZ
        BOLIVIA            ->    BO
        BRAZIL             ->    BR
        BRUNEI_DARUSSALAM  ->    BN
        BULGARIA           ->    BG
        CANADA             ->    CA
        CHILE              ->    CL
        CHINA              ->    CN
        COLOMBIA           ->    CO
        COSTA_RICA         ->    CR
        CROATIA            ->    HR
        CYPRUS             ->    CY
        CZECH              ->    CZ
        DENMARK            ->    DK
        DOMINICAN_REPUBLIC ->    DO
        ECUADOR            ->    EC
        EGYPT              ->    EG
        EL_SALVADOR        ->    SV
        ESTONIA            ->    EE
        FINLAND            ->    FI
        FRANCE             ->    FR
        FRANCE2            ->    F2
        GEORGIA            ->    GE
        GERMANY            ->    DE
        GREECE             ->    GR
        GUATEMALA          ->    GT
        HONDURAS           ->    HN
        HONG_KONG          ->    HK
        HUNGARY            ->    HU
        ICELAND            ->    IS
        INDIA              ->    IN
        INDONESIA          ->    ID
        IRAN               ->    IR
        IRELAND            ->    IE
        ISRAEL             ->    IL
        ITALY              ->    IT
        JAPAN              ->    JP
        JAPAN1             ->    J1
        JAPAN2             ->    J2
        JAPAN3             ->    J3
        JAPAN4             ->    J4
        JAPAN5             ->    J5
        JAPAN6             ->    J6
        JAPAN7             ->    JP
        JAPAN8             ->    JP
        JAPAN9             ->    JP
        JAPAN10            ->    JP
        JAPAN11            ->    JP
        JAPAN12            ->    JP
        JAPAN13            ->    JP
        JAPAN14            ->    JP
        JAPAN15            ->    JP
        JAPAN16            ->    JP
        JAPAN17            ->    JP
        JAPAN18            ->    JP
        JAPAN19            ->    JP
        JAPAN20            ->    JP
        JAPAN21            ->    JP
        JAPAN22            ->    JP
        JAPAN23            ->    JP
        JAPAN24            ->    JP
        JORDAN             ->    JO
        KAZAKHSTAN         ->    KZ
        KENYA              ->    KE
        KOREA_NORTH        ->    KP
        KOREA_ROC          ->    KR
        KOREA_ROC2         ->    K2
        KUWAIT             ->    KW
        LATVIA             ->    LV
        LEBANON            ->    LB
        LIECHTENSTEIN      ->    LI
        LITHUANIA          ->    LT
        LUXEMBOURG         ->    LU
        MACAU              ->    MO
        MACEDONIA          ->    MK
        MALAYSIA           ->    MY
        MEXICO             ->    MX
        MONACO             ->    MC
        MOROCCO            ->    MA
        NETHERLANDS        ->    NL
        NEW_ZEALAND        ->    NZ
        NORWAY             ->    NO
        OMAN               ->    OM
        PAKISTAN           ->    PK
        PANAMA             ->    PA
        PERU               ->    PE
        PHILIPPINES        ->    PH
        POLAND             ->    PL
        PORTUGAL           ->    PT
        PUERTO_RICO        ->    PR
        QATAR              ->    QA
        ROMANIA            ->    RO
        RUSSIA             ->    RU
        SAUDI_ARABIA       ->    SA
        SINGAPORE          ->    SG
        SLOVAKIA           ->    SK
        SLOVENIA           ->    SI
        SOUTH_AFRICA       ->    ZA
        SPAIN              ->    ES
        SWEDEN             ->    SE
        SWITZERLAND        ->    CH
        SYRIA              ->    SY
        TAIWAN             ->    TW
        THAILAND           ->    TH
        TRINIDAD_Y_TOBAGO  ->    TT
        TUNISIA            ->    TN
        TURKEY             ->    TR
        UKRAINE            ->    UA
        UAE                ->    AE
        UNITED_KINGDOM     ->    GB
        UNITED_STATES      ->    US
        UNITED_STATES_FCC49 ->   US
        URUGUAY             ->   UY
        UZBEKISTAN          ->   UZ
        VENEZUELA           ->   VE
        VIET_NAM            ->   VN
        YEMEN               ->   YE
        ZIMBABWE            ->   ZW"
    SYNTAX OCTET STRING (SIZE (2))


RuckusFequency ::= TEXTUAL-CONVENTION
    STATUS current
    DESCRIPTION
        "This data type represents the frequency value that are
        expressed in MHz. Units are in thousands of a MHz.

        2412 - 5805 MHz

        For example:
        2.412 GHz would be represented as 2412 MHz"
    SYNTAX Integer32 (2412..5805)


RuckusWPAPassPhrase ::= TEXTUAL-CONVENTION
    STATUS current
    DESCRIPTION
        "Specifies the WPA PSK (Wi-Fi Protected Access
        Pre Shared key).

        If the key length is 64 then all 64 characters should be in hex,
        otherwise the key assumed to be ascii."
    SYNTAX OCTET STRING (SIZE (8..63 | 64))


RuckusSSID ::= TEXTUAL-CONVENTION
    STATUS current
    DESCRIPTION
        "Ruckus service set identifier."
    SYNTAX OCTET STRING (SIZE (2..32))


RuckusRate ::= TEXTUAL-CONVENTION
    STATUS current
    DESCRIPTION
        "This attribute shall specify the set of data rates
        at which the station may transmit data.  Each octet
        contains a value representing a rate.  Each rate
        shall be within the range from 2 to 127,
        corresponding to data rates in increments of
        500 kb/s from 1 Mb/s to 63.5 Mb/s, and shall be
        supported (as indicated in the supported rates
        table) for receiving data. This value is reported in
        transmitted Beacon, Probe Request, Probe Response,
        Association Request, Association Response,
        Reassociation Request, and Reassociation Response
        frames, and is used to determine whether a BSS
        with which the station desires to synchronize is
        suitable. It is also used when starting a BSS,
        as specified in  10.3."
    SYNTAX OCTET STRING (SIZE (1..126))


RuckusdB ::= TEXTUAL-CONVENTION
    STATUS current
    DESCRIPTION
        "Used to express values of type dB."
    SYNTAX Integer32

RuckusWLANServiceType ::= TEXTUAL-CONVENTION
    STATUS current
    DESCRIPTION
        "The WLAN Service types supported on Ruckus Wireless systems."
    SYNTAX INTEGER {
            standardUsage(1),
            guestAccess(2),
            hotSpotService(3) }

RuckusAuthenticationType ::= TEXTUAL-CONVENTION
    STATUS current
    DESCRIPTION
        "The Authentication types supported on Ruckus Wireless systems."
    SYNTAX INTEGER {
            open(1),
            shared(2),
            eap(3),
            mac-address(4),
            eap-mac-mix(5) }

RuckusEncryptionType ::= TEXTUAL-CONVENTION
    STATUS current
    DESCRIPTION
        "The Encryption types supported on Ruckus Wireless systems."
    SYNTAX INTEGER {
            wpa(1),
            wpa2(2),
            wpa-Mixed(3),
            wep-64(4),
            wep-128(5),
            none-enc(6) }

RuckusWPACipherType ::= TEXTUAL-CONVENTION
    STATUS current
    DESCRIPTION
        "The WPA Encryption Cipher methods supported on Ruckus Wireless systems."
    SYNTAX INTEGER {
            tkip(1),
            aes(2),
            auto(3),
            none(4) }

RuckusWLANServicePriority ::= TEXTUAL-CONVENTION
    STATUS current
    DESCRIPTION
        "The LAN QoS Service levels supported on Ruckus Wireless systems."
    SYNTAX INTEGER {
            high(1),
            low(2) }
    
RuckusSysLogLevel ::= TEXTUAL-CONVENTION
    STATUS current
    DESCRIPTION
        "The sysLog reporting levels supported on Ruckus Wireless systems."
    SYNTAX INTEGER {
            more(1),
            warning-and-critical(2),
            critical-only(3)       }

RuckusSNMPv3AuthenticationType ::= TEXTUAL-CONVENTION
    STATUS current
    DESCRIPTION
        "The SNMP v3 authentication type supported on Ruckus Wireless systems."
    SYNTAX INTEGER {
            md5(1),
            sha(2)
                   }

RuckusSNMPv3EncryptionType ::= TEXTUAL-CONVENTION
    STATUS current
    DESCRIPTION
        "The SNMP v3 encryption type supported on Ruckus Wireless systems."
    SYNTAX INTEGER {
            des(1),
            aes(2)
                   }

RuckusSNMPVersionType ::= TEXTUAL-CONVENTION
    STATUS current
    DESCRIPTION
        "The SNMP Version type supported on Ruckus Wireless systems."
    SYNTAX INTEGER {
            v2(1),
            v3(2)
                   }

RuckusNameString ::= TEXTUAL-CONVENTION
    STATUS current
    DESCRIPTION
        "The general (128 characters) Name String defined on Ruckus Wireless systems."
    SYNTAX OCTET STRING (SIZE (1..128))

RuckusPassPhrase ::= TEXTUAL-CONVENTION
    STATUS current
    DESCRIPTION
        "The general (64 characters) passphrase defined on Ruckus Wireless systems."
    SYNTAX OCTET STRING (SIZE (8..64))

RuckusAAAServiceType ::= TEXTUAL-CONVENTION	
    STATUS current
    DESCRIPTION
        "The Ruckus AAA Server Service type."
    SYNTAX INTEGER {
            active-directory(1),
            ldap-directory(2),
            aaa-authentication(3),       
	    aaa-accounting(4) }

RuckusAPIpAddressSettingMode ::= TEXTUAL-CONVENTION
    STATUS current
    DESCRIPTION
        "The AP IP address setting mode, 
	admin-by-zd   : ZD configure the AP IP address,
	admin-by-dhcp : DHCP server configure the AP IP address,
	admin-by-ap   : AP configure its IP address locally."
    SYNTAX INTEGER {
            admin-by-zd(1),
            admin-by-dhcp(2),
            admin-by-ap(3)       }

RuckusAPRadioType ::= TEXTUAL-CONVENTION
    STATUS current
    DESCRIPTION
        "The Ruckus AP unit wireless Radio type."
    SYNTAX INTEGER {
            ieee80211bg(1),
            ieee80211na(2),
            ieee80211a(3),       
	    ieee80211n(4) }

RuckusAPRadioType24 ::= TEXTUAL-CONVENTION
    STATUS current
    DESCRIPTION
        "The Ruckus AP unit wireless Radio type 2.4G."
    SYNTAX INTEGER {
            ieee80211b(1),
            ieee80211g(2),
            ieee80211bg(3),       
	    ieee80211ng(4) }	    

RuckusAPRadioType5 ::= TEXTUAL-CONVENTION
    STATUS current
    DESCRIPTION
        "The Ruckus AP unit wireless Radio type 5G."
    SYNTAX INTEGER {
            ieee80211a(1),
            ieee80211n(2),
            ieee80211nag(3)}		    

RuckusAPRadioTxPowerLevel ::= TEXTUAL-CONVENTION
    STATUS current
    DESCRIPTION
        "The Ruckus AP unit wireless Radio Tx Power level setting."
    SYNTAX INTEGER {
            auto(1),
            full(2),
            half-full(3),
            quarter-full(4),
            one-eighth-full(5),
            one-tenth-full(6) }

RuckusAPWirelessChannel ::= TEXTUAL-CONVENTION
    STATUS current
    DESCRIPTION
        "The AP radio channel, selectable 0, 1-11, 
	0    : auto channel selection,
        1-11 : specific channel selection."
    SYNTAX Integer32 (0..11)

RuckusAPMeshConfigurationMode ::= TEXTUAL-CONVENTION
    STATUS current
    DESCRIPTION
        "The Ruckus AP unit Mesh wireless configuration mode."
    SYNTAX INTEGER {
            auto(1),
            root-ap(2),
            mesh-ap(3),       
	    disabled(4) }

RuckusAPUplinkSelectionMode ::= TEXTUAL-CONVENTION
    STATUS current
    DESCRIPTION
        "The Ruckus AP unit wireless uplink selection mode."
    SYNTAX INTEGER {
            smart(1),
	    manual(2) }

RuckusAPApproveMode ::= TEXTUAL-CONVENTION
    STATUS current
    DESCRIPTION
        "ZD managed AP approve mode."
    SYNTAX INTEGER {
            approved(1),
            not-approved(2) }

RuckusAuthStatusType ::= TEXTUAL-CONVENTION
     STATUS current
     DESCRIPTION
        "The authorized status."
     SYNTAX INTEGER {
             unauthorized(1),
             authorized(2)}

RuckusWLANAuthMethodType ::= TEXTUAL-CONVENTION
    STATUS current
    DESCRIPTION
        "Specifies the security mode.
        if wep, only open;
        if wpa, open,wpa-eap-802-1x,auto ; for auto,is open,wpa-eap-802-1x"
     SYNTAX INTEGER {
             open(1),
             wep-shared(2),
            auto(3),
            wpa-eap-802-1x(4)}

RuckusWLANEncryptionType ::= TEXTUAL-CONVENTION
    STATUS current
    DESCRIPTION
        "Specifies the security mode of this WLAN."
     SYNTAX INTEGER {
             open(1),
             wep(2),
            wpa(3)}

RuckusChannelWidthType ::= TEXTUAL-CONVENTION
    STATUS current
    DESCRIPTION
        "Specifies the channel width."
     SYNTAX INTEGER {
             cw10(10),
             cw20(20),
             cw2040(2040),
            cw40(40),
            cw80(80)}


RuckusZDAPManagementAdminControl ::= TEXTUAL-CONVENTION
    STATUS current
    DESCRIPTION
        "The ZD management control of an AP."
    SYNTAX INTEGER {
            delete(1),
            associated(2) }

RuckusSystemNodeStatus ::= TEXTUAL-CONVENTION
    STATUS current
    DESCRIPTION
        "The System status."
     SYNTAX INTEGER {
             out-of-service(0),
            in-service(8)}

RuckusSystemClusterStatus ::= TEXTUAL-CONVENTION
    STATUS current
    DESCRIPTION
        "The Cluster status."
     SYNTAX INTEGER {
             in-service(0),
             out-of-service(1),
            maintenance(2),
            network-partition-suspected(4) }

RuckusUUID ::= TEXTUAL-CONVENTION
    DISPLAY-HINT "4x-2x-2x-2x-6x"
    STATUS current
    DESCRIPTION
        "Represents a UUID over 16 hex number"
    SYNTAX       OCTET STRING (SIZE (16))

RuckusMeshRoles ::= TEXTUAL-CONVENTION
    STATUS current
    DESCRIPTION
        "AP Mesh Roles."
     SYNTAX INTEGER {
             disable(0),
             rap(1),
            map(2),
            emap(3),
            mesh-is-down(4),
            mesh-role-is-undefined(5) }

RuckusUUIDType ::= TEXTUAL-CONVENTION
    STATUS current
    DESCRIPTION
        "UUID type of RuckusSummaryApTable index"
     SYNTAX INTEGER {
             domain(1),
             zone(2),
            apgroup(3)}

RuckusRateLimiting ::= TEXTUAL-CONVENTION
    STATUS current
    DESCRIPTION
        "Used to express values of Rate limiting."
    SYNTAX INTEGER {
            disable(0), 
            rate100Kbps(1), 
            rate250Kbps(2), 
            rate500Kbps(3), 
            rate1Mbps(4), 
            rate2Mbps(5), 
            rate5Mbps(6), 
            rate10Mbps(7), 
            rate20Mbps(8), 
            rate50Mbps(9) }

-- Scalars and Tables
--

ruckusTCObjects OBJECT IDENTIFIER   ::= { ruckusTCMIB 1 }

-- Notification Types
--

ruckusTCEvents OBJECT IDENTIFIER    ::= { ruckusTCMIB 2 }

-- Conformance
--

ruckusTCConf OBJECT IDENTIFIER  ::= { ruckusTCMIB 3 }

-- Groups
--

ruckusTCGroups OBJECT IDENTIFIER    ::= { ruckusTCConf 1 }

-- Compliance
--

ruckusTCCompls OBJECT IDENTIFIER    ::= { ruckusTCConf 2 }

END
